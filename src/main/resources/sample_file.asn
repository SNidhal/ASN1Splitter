CDRF-R9
DEFINITIONS IMPLICIT TAGS	::=

BEGIN


CallEventRecord	::= --snacc isMetadata:"TRUE" -- CHOICE
{
	sgsnPDPRecord				[20] SGSNPDPRecord,
	ggsnPDPRecord				[21] GGSNPDPRecord,
	sgsnMMRecord				[22] SGSNMMRecord,
	sgsnSMORecord				[23] SGSNSMORecord,
	sgsnSMTRecord				[24] SGSNSMTRecord,
	sgsnLCTRecord				[25] SGSNLCTRecord,
	sgsnLCORecord				[26] SGSNLCORecord,
	sgsnLCNRecord				[27] SGSNLCNRecord,
	egsnPDPRecord				[70] EGSNPDPRecord,
	sgsnMBMSRecord				[76] SGSNMBMSRecord,
	ggsnMBMSRecord				[77] GGSNMBMSRecord,
	sGWRecord				[78] SGWRecord,
	pGWRecord				[79] PGWRecord
}

GGSNPDPRecord 	::= SET
{
	recordType				[0] CallEventRecordType,
	networkInitiation			[1] NetworkInitiatedPDPContext OPTIONAL,
	servedIMSI				[3] IMSI,
	ggsnAddress				[4] GSNAddress,
	chargingID				[5] ChargingID,
	sgsnAddress				[6] SEQUENCE OF GSNAddress,
	accessPointNameNI			[7] AccessPointNameNI OPTIONAL,
	pdpType					[8] PDPType OPTIONAL,
	servedPDPAddress			[9] PDPAddress OPTIONAL,
	dynamicAddressFlag			[11] DynamicAddressFlag OPTIONAL,
	listOfTrafficVolumes			[12] SEQUENCE OF ChangeOfCharCondition OPTIONAL,
	recordOpeningTime			[13] TimeStamp,
	duration				[14] CallDuration,
	causeForRecClosing			[15] CauseForRecClosing,
	diagnostics				[16] Diagnostics OPTIONAL,
	recordSequenceNumber			[17] INTEGER OPTIONAL,
	nodeID					[18] NodeID OPTIONAL,
	recordExtensions			[19] ContentInfo OPTIONAL,
	localSequenceNumber			[20] LocalSequenceNumber OPTIONAL,
	apnSelectionMode			[21] APNSelectionMode OPTIONAL,
	servedMSISDN				[22] MSISDN OPTIONAL,
	chargingCharacteristics	    		[23] ChargingCharacteristics,
	chChSelectionMode			[24] ChChSelectionMode OPTIONAL,
	iMSsignalingContext			[25] NULL OPTIONAL,
	externalChargingID			[26] OCTET STRING OPTIONAL,	
	sgsnPLMNIdentifier			[27] PLMN-Id OPTIONAL,
	servedIMEISV				[29] IMEI OPTIONAL,
	rATType					[30] RATType OPTIONAL,
	mSTimeZone 				[31] MSTimeZone OPTIONAL,
	userLocationInformation			[32] OCTET STRING OPTIONAL,
	cAMELChargingInformation		[33] OCTET STRING OPTIONAL
	
}

EGSNPDPRecord 	::= SET
{
	recordType			[0] CallEventRecordType,
	networkInitiation		[1] NetworkInitiatedPDPContext OPTIONAL,
	servedIMSI			[3] IMSI,
	ggsnAddress			[4] GSNAddress,
	chargingID			[5] ChargingID,
	sgsnAddress			[6] SEQUENCE OF GSNAddress,
	accessPointNameNI		[7] AccessPointNameNI OPTIONAL,
	pdpType				[8] PDPType OPTIONAL,
	servedPDPAddress		[9] PDPAddress OPTIONAL,
	dynamicAddressFlag		[11] DynamicAddressFlag OPTIONAL,
	listOfTrafficVolumes		[12] SEQUENCE OF ChangeOfCharCondition OPTIONAL,
	recordOpeningTime		[13] TimeStamp,
	duration			[14] CallDuration,
	causeForRecClosing		[15] CauseForRecClosing,
	diagnostics			[16] Diagnostics OPTIONAL,
	recordSequenceNumber		[17] INTEGER OPTIONAL,
	nodeID				[18] NodeID OPTIONAL,
	recordExtensions		[19] ContentInfo OPTIONAL,
	localSequenceNumber		[20] LocalSequenceNumber OPTIONAL,
	apnSelectionMode		[21] APNSelectionMode OPTIONAL,
	servedMSISDN			[22] MSISDN OPTIONAL,
	chargingCharacteristics		[23] ChargingCharacteristics,
	chChSelectionMode		[24] ChChSelectionMode OPTIONAL,
	iMSsignalingContext		[25] NULL OPTIONAL,
	externalChargingID		[26] OCTET STRING OPTIONAL,
	sgsnPLMNIdentifier		[27] PLMN-Id OPTIONAL,
	pSFurnishChargingInformation	[28] PSFurnishChargingInformation OPTIONAL,
	servedIMEISV			[29] IMEI OPTIONAL,
	rATType				[30] RATType OPTIONAL,
	mSTimeZone 			[31] MSTimeZone OPTIONAL,
	userLocationInformation		[32] OCTET STRING OPTIONAL,
	cAMELChargingInformation	[33] OCTET STRING OPTIONAL,
	listOfServiceData		[34] SEQUENCE OF ChangeOfServiceCondition OPTIONAL
}

SGSNMMRecord	::= SET
{
	recordType			[0] CallEventRecordType,
	servedIMSI			[1] IMSI,
	servedIMEI			[2] IMEI OPTIONAL,
	sgsnAddress			[3] GSNAddress OPTIONAL,
	msNetworkCapability		[4] MSNetworkCapability OPTIONAL,
	routingArea			[5] RoutingAreaCode OPTIONAL,
	locationAreaCode		[6] LocationAreaCode OPTIONAL,
	cellIdentifier			[7] CellId OPTIONAL,
	changeLocation			[8] SEQUENCE OF ChangeLocation OPTIONAL,
	recordOpeningTime		[9] TimeStamp,
	duration			[10] CallDuration OPTIONAL, 
	sgsnChange			[11] SGSNChange OPTIONAL,
	causeForRecClosing		[12] CauseForRecClosing,
	diagnostics			[13] Diagnostics OPTIONAL,
	recordSequenceNumber		[14] INTEGER OPTIONAL,
	nodeID				[15] NodeID OPTIONAL,
	recordExtensions		[16] ManagementExtensions OPTIONAL,
	localSequenceNumber		[17] LocalSequenceNumber OPTIONAL,
	servedMSISDN			[18] MSISDN OPTIONAL,
	chargingCharacteristics	    	[19] ChargingCharacteristics,	
	cAMELInformationMM 		[20] CAMELInformationMM OPTIONAL,
	rATType				[21] RATType OPTIONAL,
	chChSelectionMode		[22] ChChSelectionMode OPTIONAL,
	cellPLMNId			[23] PLMN-Id OPTIONAL
}

SGSNPDPRecord 	::= SET
{
	recordType			[0] CallEventRecordType,
	networkInitiation		[1] NetworkInitiatedPDPContext OPTIONAL,
	servedIMSI			[3] IMSI,
	servedIMEI			[4] IMEI OPTIONAL,
	sgsnAddress			[5] GSNAddress OPTIONAL,
	msNetworkCapability		[6] MSNetworkCapability OPTIONAL,
	routingArea			[7] RoutingAreaCode OPTIONAL,
	locationAreaCode		[8] LocationAreaCode OPTIONAL,
	cellIdentifier			[9] CellId OPTIONAL,
	chargingID			[10] ChargingID,
	ggsnAddressUsed			[11] GSNAddress,
	accessPointNameNI		[12] AccessPointNameNI OPTIONAL,
	pdpType				[13] PDPType OPTIONAL,
	servedPDPAddress		[14] PDPAddress OPTIONAL,
	listOfTrafficVolumes		[15] SEQUENCE OF ChangeOfCharCondition 	OPTIONAL,
	recordOpeningTime		[16] TimeStamp,
	duration			[17] CallDuration,
	sgsnChange			[18] SGSNChange OPTIONAL,
	causeForRecClosing		[19] CauseForRecClosing,
	diagnostics			[20] Diagnostics OPTIONAL,
	recordSequenceNumber		[21] INTEGER OPTIONAL,
	nodeID				[22] NodeID OPTIONAL,
	recordExtensions		[23] ManagementExtensions OPTIONAL,
	localSequenceNumber		[24] LocalSequenceNumber OPTIONAL,
	apnSelectionMode		[25] APNSelectionMode OPTIONAL,
	accessPointNameOI		[26] AccessPointNameOI OPTIONAL,
	servedMSISDN			[27] MSISDN OPTIONAL,
	chargingCharacteristics	    	[28] ChargingCharacteristics,
	rATType				[29] RATType OPTIONAL,
	cAMELInformationPDP  		[30] CAMELInformationPDP OPTIONAL,
	rNCUnsentDownlinkVolume	    	[31] DataVolumeGPRS OPTIONAL,
	chChSelectionMode		[32] ChChSelectionMode OPTIONAL,
	dynamicAddressFlag		[33] DynamicAddressFlag OPTIONAL,
	iMSIunauthenticatedFlag 	[34] NULL OPTIONAL,
	userCSGInformation		[35] UserCSGInformation OPTIONAL,
	servedPDPPDNAddressExt 		[36] PDPAddress OPTIONAL,
	sgsnPLMNIdentifier		[40] PLMN-Id OPTIONAL
}

SGSNSMORecord	::= SET
{
	recordType			[0] CallEventRecordType,
	servedIMSI			[1] IMSI,
	servedIMEI			[2] IMEI OPTIONAL,
	servedMSISDN			[3] MSISDN OPTIONAL,
	msNetworkCapability		[4] MSNetworkCapability OPTIONAL,
	serviceCentre			[5] AddressString OPTIONAL,
	recordingEntity			[6] RecordingEntity OPTIONAL,
	locationArea			[7] LocationAreaCode OPTIONAL,
	routingArea			[8] RoutingAreaCode OPTIONAL,
	cellIdentifier			[9] CellId OPTIONAL,
	messageReference		[10] MessageReference,
	eventTimeStamp		    	[11] TimeStamp,	
	smsResult			[12] SMSResult OPTIONAL,
	recordExtensions		[13] ManagementExtensions OPTIONAL, 
	nodeID				[14] NodeID OPTIONAL,
	localSequenceNumber		[15] LocalSequenceNumber OPTIONAL,
	chargingCharacteristics	    	[16] ChargingCharacteristics,
	rATType				[17] RATType OPTIONAL,
	destinationNumber		[18] SmsTpDestinationNumber  OPTIONAL,
	cAMELInformationSMS		[19] CAMELInformationSMS OPTIONAL,
	chChSelectionMode		[20] ChChSelectionMode OPTIONAL
}

SGSNSMTRecord	::= SET
{
	recordType			[0] CallEventRecordType,
	servedIMSI			[1] IMSI,
	servedIMEI			[2] IMEI OPTIONAL,
	servedMSISDN			[3] MSISDN OPTIONAL,
	msNetworkCapability	    	[4] MSNetworkCapability OPTIONAL,
	serviceCentre			[5] AddressString OPTIONAL,
	recordingEntity		    	[6] RecordingEntity OPTIONAL,
	locationArea			[7] LocationAreaCode OPTIONAL,
	routingArea			[8] RoutingAreaCode OPTIONAL,
	cellIdentifier			[9] CellId OPTIONAL,
	eventTimeStamp		   	[10] TimeStamp,	
	smsResult			[11] SMSResult OPTIONAL,
	recordExtensions		[12] ManagementExtensions OPTIONAL,
	nodeID				[13] NodeID OPTIONAL,
	localSequenceNumber	    	[14] LocalSequenceNumber OPTIONAL,
	chargingCharacteristics		[15] ChargingCharacteristics,
	rATType				[16] RATType OPTIONAL,
	chChSelectionMode		[17] ChChSelectionMode OPTIONAL,
	cAMELInformationSMS		[18] CAMELInformationSMS OPTIONAL
}

SGSNLCTRecord	::= SET
{
	recordType			[0] CallEventRecordType,
	recordingEntity			[1] RecordingEntity,
	lcsClientType			[2] LCSClientType,
	lcsClientIdentity		[3] LCSClientIdentity,
	servedIMSI			[4] IMSI,
	servedMSISDN			[5] MSISDN OPTIONAL,
	sgsnAddress			[6] GSNAddress OPTIONAL,
	locationType			[7] LocationType,
	lcsQos				[8] LCSQoSInfo OPTIONAL,
	lcsPriority			[9] LCS-Priority OPTIONAL,
	mlcNumber			[10] ISDN-AddressString,
	eventTimeStamp			[11] TimeStamp,
	measurementDuration		[12] CallDuration OPTIONAL,
	notificationToMSUser		[13] NotificationToMSUser OPTIONAL,
	privacyOverride			[14] NULL OPTIONAL,
	location			[15] LocationAreaAndCell OPTIONAL,
	routingArea			[16] RoutingAreaCode OPTIONAL,
	locationEstimate		[17] Ext-GeographicalInformation OPTIONAL,
	positioningData			[18] PositioningData OPTIONAL,
	lcsCause			[19] LCSCause OPTIONAL,
	diagnostics			[20] Diagnostics OPTIONAL,
	nodeID				[21] NodeID OPTIONAL,
	localSequenceNumber	    	[22] LocalSequenceNumber OPTIONAL,
	chargingCharacteristics		[23] ChargingCharacteristics,
	chChSelectionMode		[24] ChChSelectionMode OPTIONAL,
	rATType				[25] RATType OPTIONAL,
	recordExtensions		[26] ManagementExtensions OPTIONAL,
	causeForRecClosing		[27] CauseForRecClosing
}

SGSNLCORecord	::= SET
{
	recordType			[0] CallEventRecordType,
	recordingEntity			[1] RecordingEntity,
	lcsClientType			[2] LCSClientType OPTIONAL,
	lcsClientIdentity		[3] LCSClientIdentity OPTIONAL,
	servedIMSI			[4] IMSI,
	servedMSISDN			[5] MSISDN OPTIONAL,
	sgsnAddress			[6] GSNAddress OPTIONAL,
	locationMethod			[7] LocationMethod,
	lcsQos				[8] LCSQoSInfo OPTIONAL,
	lcsPriority			[9] LCS-Priority OPTIONAL,
	mlcNumber			[10] ISDN-AddressString OPTIONAL,
	eventTimeStamp			[11] TimeStamp,
	measurementDuration		[12] CallDuration OPTIONAL,
	location			[13] LocationAreaAndCell OPTIONAL,
	routingArea			[14] RoutingAreaCode OPTIONAL,
	locationEstimate		[15] Ext-GeographicalInformation OPTIONAL,
	positioningData			[16] PositioningData OPTIONAL,
	lcsCause			[17] LCSCause OPTIONAL,
	diagnostics			[18] Diagnostics OPTIONAL,
	nodeID				[19] NodeID OPTIONAL,
	localSequenceNumber	    	[20] LocalSequenceNumber OPTIONAL,
	chargingCharacteristics		[21] ChargingCharacteristics,
	chChSelectionMode		[22] ChChSelectionMode OPTIONAL,
	rATType				[23] RATType OPTIONAL,
	recordExtensions		[24] ManagementExtensions OPTIONAL,
	causeForRecClosing		[25] CauseForRecClosing
}

SGSNLCNRecord	::= SET
{
	recordType			[0] CallEventRecordType,
	recordingEntity			[1] RecordingEntity,
	lcsClientType			[2] LCSClientType OPTIONAL,
	lcsClientIdentity		[3] LCSClientIdentity OPTIONAL,
	servedIMSI			[4] IMSI OPTIONAL,
	servedMSISDN			[5] MSISDN OPTIONAL,
	sgsnAddress			[6] GSNAddress OPTIONAL,
	servedIMEI			[7] IMEI OPTIONAL,	
	lcsQos				[8] LCSQoSInfo OPTIONAL,
	lcsPriority			[9] LCS-Priority OPTIONAL,
	mlcNumber			[10] ISDN-AddressString OPTIONAL,
	eventTimeStamp			[11] TimeStamp,
	measurementDuration		[12] CallDuration OPTIONAL,
	location			[13] LocationAreaAndCell OPTIONAL,
	routingArea			[14] RoutingAreaCode OPTIONAL,
	locationEstimate		[15] Ext-GeographicalInformation OPTIONAL,
	positioningData			[16] PositioningData OPTIONAL,
	lcsCause			[17] LCSCause OPTIONAL,
	diagnostics			[18] Diagnostics OPTIONAL,
	nodeID				[19] NodeID OPTIONAL,
	localSequenceNumber	    	[20] LocalSequenceNumber OPTIONAL,
	chargingCharacteristics		[21] ChargingCharacteristics,
	chChSelectionMode		[22] ChChSelectionMode OPTIONAL,
	rATType				[23] RATType OPTIONAL,
	recordExtensions		[24] ManagementExtensions OPTIONAL,
	causeForRecClosing		[25] CauseForRecClosing
}


SGSNMBMSRecord 	::= SET
{
	recordType			[0] CallEventRecordType,
	ggsnAddress			[1] GSNAddress,
	chargingID			[2] ChargingID,
	listofRAs			[3] SEQUENCE OF RAIdentity OPTIONAL,
	accessPointNameNI		[4] AccessPointNameNI OPTIONAL,
	servedPDPAddress		[5] PDPAddress OPTIONAL,
	listOfTrafficVolumes		[6] SEQUENCE OF ChangeOfMBMSCondition OPTIONAL,
	recordOpeningTime		[7] TimeStamp,
	duration			[8] CallDuration,
	causeForRecClosing		[9] CauseForRecClosing,
	diagnostics			[10] Diagnostics OPTIONAL,
	recordSequenceNumber		[11] INTEGER OPTIONAL,
	nodeID				[12] NodeID OPTIONAL,
	recordExtensions		[13] ManagementExtensions OPTIONAL,
	localSequenceNumber		[14] LocalSequenceNumber OPTIONAL,
	sgsnPLMNIdentifier		[15] PLMN-Id OPTIONAL,
	numberofReceivingUE		[16] INTEGER OPTIONAL,
	mbmsInformation			[17] MBMSInformation OPTIONAL
}

GGSNMBMSRecord 	::= SET
{
	recordType			[0] CallEventRecordType,
	ggsnAddress			[1] GSNAddress,
	chargingID			[2] ChargingID,
	listofDownstreamNodes		[3] SEQUENCE OF GSNAddress,
	accessPointNameNI		[4] AccessPointNameNI OPTIONAL,
	servedPDPAddress		[5] PDPAddress OPTIONAL,
	listOfTrafficVolumes		[6] SEQUENCE OF ChangeOfMBMSCondition OPTIONAL,
	recordOpeningTime		[7] TimeStamp,
	duration			[8] CallDuration,
	causeForRecClosing		[9] CauseForRecClosing,
	diagnostics			[10] Diagnostics OPTIONAL,
	recordSequenceNumber		[11] INTEGER OPTIONAL,
	nodeID				[12] NodeID OPTIONAL,
	recordExtensions		[13] ManagementExtensions OPTIONAL,
	localSequenceNumber		[14] LocalSequenceNumber OPTIONAL,
	mbmsInformation			[15] MBMSInformation OPTIONAL
}

SGWRecord	::= SET
{
	recordType			[0] CallEventRecordType,
	networkInitiation		[1] NetworkInitiatedPDPContext OPTIONAL,
	servedIMSI			[3] IMSI,
	sGWAddress			[4] GSNAddress,
	chargingID			[5] ChargingID,
	servingNodeAddress		[6] SEQUENCE OF GSNAddress  OPTIONAL,
	accessPointNameNI		[7] AccessPointNameNI OPTIONAL,
	pdpPDNType			[8] PDPType OPTIONAL,
	servedPDPPDNAddress		[9] PDPAddress OPTIONAL,
	dynamicAddressFlag		[11] DynamicAddressFlag OPTIONAL,
	listOfTrafficVolumes		[12] SEQUENCE OF ChangeOfCharCondition OPTIONAL,   
	recordOpeningTime		[13] TimeStamp,
	duration			[14] CallDuration,
	causeForRecClosing		[15] CauseForRecClosing,
	diagnostics			[16] Diagnostics OPTIONAL,
	recordSequenceNumber		[17] INTEGER OPTIONAL,
	nodeID				[18] NodeID OPTIONAL,
	recordExtensions		[19] ContentInfo OPTIONAL,
	localSequenceNumber		[20] LocalSequenceNumber OPTIONAL,
	apnSelectionMode		[21] APNSelectionMode OPTIONAL,
	servedMSISDN			[22] MSISDN OPTIONAL,
	chargingCharacteristics		[23] ChargingCharacteristics,
	chChSelectionMode		[24] ChChSelectionMode OPTIONAL,
	iMSsignalingContext		[25] NULL OPTIONAL,
	servingNodePLMNIdentifier	[27] PLMN-Id OPTIONAL,
	servedIMEISV			[29] IMEI OPTIONAL,
	rATType				[30] RATType OPTIONAL,
	mSTimeZone 			[31] MSTimeZone OPTIONAL,
	userLocationInformation		[32] OCTET STRING OPTIONAL,
	cAMELChargingInformation	[33] OCTET STRING OPTIONAL,
	sGWChange			[34] SGWChange OPTIONAL,
	servingNodeType			[35] SEQUENCE OF ServingNodeType OPTIONAL,
	pGWAddressUsed			[36] GSNAddress OPTIONAL,
	pGWPLMNIdentifier		[37] PLMN-Id OPTIONAL,
	startTime			[38] TimeStamp OPTIONAL,
	stopTime			[39] TimeStamp OPTIONAL,
	pDNConnectionID			[40] ChargingID OPTIONAL,
	iMSIunauthenticatedFlag 	[41] NULL OPTIONAL,
	userCSGInformation		[42] UserCSGInformation OPTIONAL,
	servedPDPPDNAddressExt 		[43] PDPAddress OPTIONAL,
        listOfRANSecondaryRATUsageReports [64] SEQUENCE OF RANSecondaryRATUsageReport OPTIONAL
}

PGWRecord	::= SET
{
	recordType			[0] CallEventRecordType,
	servedIMSI			[3] IMSI,
	pGWAddress			[4] GSNAddress,
	chargingID			[5] ChargingID,
	servingNodeAddress		[6] SEQUENCE OF GSNAddress,
	accessPointNameNI		[7] AccessPointNameNI OPTIONAL,
	pdpPDNType			[8] PDPType OPTIONAL,
	servedPDPPDNAddress		[9] PDPAddress OPTIONAL,
	dynamicAddressFlag		[11] DynamicAddressFlag OPTIONAL,
	listOfTrafficVolumes		[12] SEQUENCE OF ChangeOfCharCondition OPTIONAL,
	recordOpeningTime		[13] TimeStamp,
	duration			[14] CallDuration,
	causeForRecClosing		[15] CauseForRecClosing,
	diagnostics			[16] Diagnostics OPTIONAL,
	recordSequenceNumber		[17] INTEGER OPTIONAL,
	nodeID				[18] NodeID OPTIONAL,
	recordExtensions		[19] ContentInfo OPTIONAL,
	localSequenceNumber		[20] LocalSequenceNumber OPTIONAL,
	apnSelectionMode		[21] APNSelectionMode OPTIONAL,
	servedMSISDN			[22] MSISDN OPTIONAL,
	chargingCharacteristics		[23] ChargingCharacteristics,
	chChSelectionMode		[24] ChChSelectionMode OPTIONAL,
	iMSsignalingContext		[25] NULL OPTIONAL,
	externalChargingID		[26] OCTET STRING OPTIONAL,
	servingNodePLMNIdentifier	[27] PLMN-Id OPTIONAL,
	pSFurnishChargingInformation	[28] PSFurnishChargingInformation OPTIONAL,
	servedIMEISV			[29] IMEI OPTIONAL,
	rATType				[30] RATType OPTIONAL,
	mSTimeZone 			[31] MSTimeZone OPTIONAL,
	userLocationInformation		[32] OCTET STRING OPTIONAL,
	cAMELChargingInformation	[33] OCTET STRING OPTIONAL,
	listOfServiceData		[34] SEQUENCE OF ChangeOfServiceConditions OPTIONAL,
	servingNodeType			[35] SEQUENCE OF  ServingNodeType OPTIONAL,
        servedMNNAI			[36] SubscriptionID OPTIONAL,
	pGWPLMNIdentifier		[37] PLMN-Id OPTIONAL,
	startTime			[38] TimeStamp OPTIONAL,
	stopTime			[39] TimeStamp OPTIONAL,
	served3gpp2MEID			[40] OCTET STRING OPTIONAL,
	pDNConnectionID			[41] ChargingID OPTIONAL,
    	iMSIunauthenticatedFlag 		[42] NULL OPTIONAL,
	userCSGInformation			[43] UserCSGInformation OPTIONAL,
	threeGPP2UserLocationInformation	[44] OCTET STRING OPTIONAL,
	servedPDPPDNAddressExt 			[45] PDPAddress OPTIONAL,
        listOfRANSecondaryRATUsageReports    [73] SEQUENCE OF RANSecondaryRATUsageReport OPTIONAL
}

------------------------------------------------------------------------------
--
--  GPRS DATA TYPES
--
------------------------------------------------------------------------------

AccessPointNameNI	::= IA5String (SIZE(1..63))
	--
	-- Network Identifier part of APN in  dot representation.
	-- For example, if the complete APN is 'apn1a.apn1b.apn1c.mnc022.mcc111.gprs'
	-- NI is 'apn1a.apn1b.apn1c' and is presented in this form in the CDR..

AccessPointNameOI	::= IA5String (SIZE(1..37))
	--
	-- Operator Identifier part of APN in dot representation.
	-- In the 'apn1a.apn1b.apn1c.mnc022.mcc111.gprs' example, the OI portion is 'mnc022.mcc111.gprs'
	-- and is presented in this form in the CDR.
	--

AddressString ::= OCTET STRING (SIZE (1..maxAddressLength))
	-- This type is used to represent a number for addressing
	-- purposes. It is composed of
	--	a)	one octet for nature of address, and numbering plan
	--		indicator.
	--	b)	digits of an address encoded as TBCD-String.

	-- a)	The first octet includes a one bit extension indicator, a
	--		3 bits nature of address indicator and a 4 bits numbering
	--		plan indicator, encoded as follows:

	-- bit 8: 1  (no extension)

	-- bits 765: nature of address indicator
	--	000  unknown
	--	001  international number
	--	010  national significant number
	--	011  network specific number
	--	100  subscriber number
	--	101  reserved
	--	110  abbreviated number
	--	111  reserved for extension

	-- bits 4321: numbering plan indicator
	--	0000  unknown
	--	0001  ISDN/Telephony Numbering Plan (Rec CCITT E.164)
	--	0010  spare
	--	0011  data numbering plan (CCITT Rec X.121)
	--	0100  telex numbering plan (CCITT Rec F.69)
	--	0101  spare
	--	0110  land mobile numbering plan (CCITT Rec E.212)
	--	0111  spare
	--	1000  national numbering plan
	--	1001  private numbering plan
	--	1111  reserved for extension

	--	all other values are reserved.

	-- b)	The following octets representing digits of an address
	--		encoded as a TBCD-STRING.	

AFChargingIdentifier ::= OCTET STRING
    --
    -- see AF-Charging-Identifier AVP as defined in TS 29.214[89]
    --

AFRecordInformation	::= SEQUENCE
{
	aFChargingIdentifier		[1] AFChargingIdentifier,
	flows						[2] Flows OPTIONAL
}

APNSelectionMode::= ENUMERATED
{
	--
	-- See Information Elements TS 29.060 [75]
	--
	mSorNetworkProvidedSubscriptionVerified	(0),
	mSProvidedSubscriptionNotVerified	(1),
	networkProvidedSubscriptionNotVerified	(2)
}

BCDDirectoryNumber		::= OCTET STRING
	-- This type contains the binary coded decimal representation of
	-- a directory number e.g. calling/called/connected/translated number.
	-- The encoding of the octet string is in accordance with the
	-- the elements "Calling party BCD number", "Called party BCD number"
	-- and "Connected number" defined in TS 24.008 [64].
	-- This encoding includes type of number and number plan information
	-- together with a BCD encoded digit string.
	-- It may also contain both a presentation and screening indicator
	-- (octet 3a).
	-- For the avoidance of doubt, this field does not include 
	-- octets 1 and 2, the element name and length, as this would be 
	-- redundant.

CallEventRecordType 	::= INTEGER 
{ 
--
--	Record values 18..22 are GPRS specific.
--	The contents are defined in TS 32.251 [11]
--
	sgsnPDPRecord		(18),
	ggsnPDPRecord		(19),
	sgsnMMRecord		(20),
	sgsnSMORecord		(21),
	sgsnSMTRecord		(22),
-- 
--  Record values 26..28 are GPRS-LCS specific.
--	The contents are defined in TS 32.251 [11]
--

	sgsnMtLCSRecord		(26),
	sgsnMoLCSRecord     	(27),
    	sgsnNiLCSRecord     	(28),
--
--  Record values 70 is for Flow based Charging
--  The contents are defined in TS 32.251 [11]
--
	egsnPDPRecord		(70),
--
--  Record values 76..79 are MBMS specific.
--  The contents are defined in TS 32.251 [11]
--  Record values 76 and 77 are MBMS bearer context specific
--
	sgsnMBMSRecord		(76),
	ggsnMBMSRecord		(77),
--
--  Record values 82..83 are EPC specific.
--  The contents are defined in TS 32.251 [11]
--
	sGWRecord		(84),
	pGWRecord		(85)
    	
}

CallingNumber			::= BCDDirectoryNumber

CallReferenceNumber ::= OCTET STRING (SIZE (1..8))

CAMELAccessPointNameNI	::= AccessPointNameNI

CAMELAccessPointNameOI	::= AccessPointNameOI

CAMELInformationMM		::= SET 
{
	sCFAddress				[1] SCFAddress OPTIONAL,
	serviceKey				[2] ServiceKey OPTIONAL,
	defaultTransactionHandling	    	[3] DefaultGPRS-Handling OPTIONAL,
	numberOfDPEncountered  		    	[4] NumberOfDPEncountered OPTIONAL,
	levelOfCAMELService			[5] LevelOfCAMELService OPTIONAL,
	freeFormatData				[6] FreeFormatData OPTIONAL,
	fFDAppendIndicator	     		[7] FFDAppendIndicator OPTIONAL
}

CAMELInformationPDP	::= SET
{
	sCFAddress				[1] SCFAddress OPTIONAL,
	serviceKey				[2] ServiceKey OPTIONAL,
	defaultTransactionHandling	    	[3] DefaultGPRS-Handling OPTIONAL,
	cAMELAccessPointNameNI		    	[4] CAMELAccessPointNameNI OPTIONAL,
	cAMELAccessPointNameOI		    	[5] CAMELAccessPointNameOI OPTIONAL,
	numberOfDPEncountered  		    	[6] NumberOfDPEncountered OPTIONAL,
	levelOfCAMELService			[7] LevelOfCAMELService OPTIONAL,
	freeFormatData				[8] FreeFormatData OPTIONAL,
	fFDAppendIndicator	     		[9] FFDAppendIndicator OPTIONAL
}

CAMELInformationSMS		::= SET 
{
	sCFAddress				[1] SCFAddress OPTIONAL,
	serviceKey				[2] ServiceKey OPTIONAL,
	defaultSMSHandling			[3] DefaultSMS-Handling OPTIONAL,
	cAMELCallingPartyNumber			[4] CallingNumber OPTIONAL,
	cAMELDestinationSubscriberNumber	[5] SmsTpDestinationNumber OPTIONAL,
	cAMELSMSCAddress			[6] AddressString OPTIONAL,
	freeFormatData				[7] FreeFormatData OPTIONAL,
	smsReferenceNumber			[8] CallReferenceNumber	OPTIONAL
}

Diagnostics					::= CHOICE
{
	gsm0408Cause				[0] INTEGER,
	-- See TS 24.008 [64]	

	gsm0902MapErrorValue			[1] INTEGER,
	-- Note: The value to be stored here corresponds to
	-- the local values defined in the MAP-Errors and 
	-- MAP-DialogueInformation modules, for full details
	-- see TS 29.002 [60].

	itu-tQ767Cause				[2] INTEGER,
	-- See ITU-T Q.767 [67]	

	networkSpecificCause			[3] ManagementExtension,
	-- To be defined by network operator	

	manufacturerSpecificCause		[4] INTEGER,
	-- To be defined by manufacturer	
	
	positionMethodFailureCause	[5] PositionMethodFailure-Diagnostic,
	-- see TS 29.002 [60]
	unauthorizedLCSClientCause	[6] UnauthorizedLCSClient-Diagnostic
	-- see TS 29.002 [60]
}

MessageReference		::= OCTET STRING

RecordingEntity 		::= AddressString

CellId	::= OCTET STRING (SIZE(2))
	--
	-- Coded according to TS 24.008 [64]	
	--

LocationAreaCode		::= OCTET STRING (SIZE(2))
	--
	-- See TS 24.008 [64]
	--

MCC-MNC		::= OCTET STRING (SIZE(3))
	--
	-- See TS 24.008 [64]
	--
	
CallDuration 			::= INTEGER
	--
	-- The call duration is counted in seconds. 
	-- For successful calls /sessions / PDP contexts, this is the chargeable duration.
	-- For call attempts this is the call holding time.
	-- 

ManagementExtensions	::= SET OF ManagementExtension


TimeStamp			::= OCTET STRING (SIZE(9))
	--
	-- The contents of this field are a compact form of the UTCTime format
	-- containing local time plus an offset to universal time. Binary coded
	-- decimal encoding is employed for the digits to reduce the storage and
	-- transmission overhead
	-- e.g. YYMMDDhhmmssShhmm
	-- where
	-- YY 	= 	Year 00 to 99		BCD encoded
	-- MM 	= 	Month 01 to 12 	BCD encoded
	-- DD	=	Day 01 to 31		BCD encoded
	-- hh	=	hour 00 to 23		BCD encoded
	-- mm	=	minute 00 to 59	BCD encoded
	-- ss	=	second 00 to 59	BCD encoded
	-- S	=	Sign 0 = "+", "-"	ASCII encoded
	-- hh	=	hour 00 to 23		BCD encoded
	-- mm	=	minute 00 to 59	BCD encoded
	--

LevelOfCAMELService		::= BIT STRING
{
	basic					(0),
	callDurationSupervision			(1),
	onlineCharging				(2)
}

DefaultGPRS-Handling ::= ENUMERATED 
{
	continueTransaction 			(0) ,
	releaseTransaction 			(1)
}
-- exception handling:
-- reception of values in range 2-31 shall be treated as "continueTransaction"
-- reception of values greater than 31 shall be treated as "releaseTransaction"

DefaultSMS-Handling ::= ENUMERATED 
{
	continueTransaction 			(0) ,
	releaseTransaction 			(1)
}
--	exception handling:
--	reception of values in range 2-31 shall be treated as "continueTransaction"
--	reception of values greater than 31 shall be treated as "releaseTransaction"

CauseForRecClosing	::= INTEGER
{
	--
	-- In GGSN the value sGSNChange should be used for partial record
	-- generation due to SGSN Address List Overflow
	-- 
	-- LCS related causes belong to the MAP error causes acc. TS 29.002 [60]
	--
	-- cause codes 0 to 15 are defined 'CauseForTerm' (cause for termination)
	--
	normalRelease				(0),
	abnormalRelease				(4),
	cAMELInitCallRelease			(5),
	volumeLimit				(16),
	timeLimit				(17),
	sGSNChange				(18),
	maxChangeCond				(19),
	managementIntervention	    		(20),
    	intraSGSNIntersystemChange		(21),
	rATChange				(22),
	mSTimeZoneChange			(23),
	sGSNPLMNIDChange 			(24),
    	unauthorizedRequestingNetwork		(52),
	unauthorizedLCSClient			(53),
	positionMethodFailure			(54),
	unknownOrUnreachableLCSClient		(58),
	listofDownstreamNodeChange		(59)
}

ChangeCondition	::= ENUMERATED
{
	--
	-- Failure Handling values used in eGCDR only
	--
	qoSChange				(0),
	tariffTime				(1),
	recordClosure				(2),
	failureHandlingContinueOngoing		(3),
	failureHandlingRetryandTerminateOngoing	(4),
	failureHandlingTerminateOngoing	   	(5),
	cGI-SAICHange				(6),
	rAIChange				(7),
	dT-Establishment			(8),
	dT-Removal				(9),
        eCGIChange				(10), 	-- bearer modification. "ECGI Change"
	tAIChange				(11), 	-- bearer modification. "TAI Change"
	userLocationChange			(12)	-- bearer modification. "User Location Change"
}

ChangeOfCharCondition	::= SEQUENCE
{
	--
	-- Used in PDP context record only
	-- failureHandlingContinue field used in eGCDR only
	--
	qosRequested				[1] QoSInformation OPTIONAL,
	qosNegotiated				[2] QoSInformation OPTIONAL,
	dataVolumeGPRSUplink			[3] DataVolumeGPRS OPTIONAL,
	dataVolumeGPRSDownlink			[4] DataVolumeGPRS OPTIONAL,
	changeCondition				[5] ChangeCondition,
	changeTime				[6] TimeStamp,
	failureHandlingContinue			[7] FailureHandlingContinue OPTIONAL,
	userLocationInformation			[8] OCTET STRING OPTIONAL,
	ePCQoSInformation			[9] EPCQoSInformation OPTIONAL
}

ChangeOfMBMSCondition	::= SEQUENCE
{
	--
	-- Used in MBMS record
	--
	qosRequested				[1] QoSInformation OPTIONAL,
	qosNegotiated				[2] QoSInformation OPTIONAL,
	dataVolumeMBMSUplink			[3] DataVolumeMBMS OPTIONAL,
	dataVolumeMBMSDownlink			[4] DataVolumeMBMS,
	changeCondition				[5] ChangeCondition,
	changeTime				[6] TimeStamp,
	failureHandlingContinue			[7] FailureHandlingContinue OPTIONAL
}


ChangeLocation	::= SEQUENCE
{
	--
	-- used in SGSNMMRecord only
	--
	locationAreaCode			[0] LocationAreaCode,
	routingAreaCode		    		[1] RoutingAreaCode,
	cellId					[2] CellId OPTIONAL,
	changeTime				[3] TimeStamp,
	mCC-MNC					[4] PLMN-Id OPTIONAL
}

ChargingCharacteristics	::= OCTET STRING (SIZE(2))
    --
	--	Bit 0-3: Profile Index
	--	Bit 4-15: For Behavior
	--

ChargingID	::= INTEGER (0..4294967295)
	--
	-- Generated in GGSN, part of PDP context, see TS 23.060 [74]
	-- 0..4294967295 is equivalent to 0..2**32-1
	--

ChChSelectionMode		::= ENUMERATED
{
	servingNodeSupplied		(0),	-- For S-GW/P-GW
	subscriptionSpecific		(1),	-- For SGSN only
	aPNSpecific			(2),	-- For SGSN only
	homeDefault			(3),	-- For SGSN, S-GW and P-GW
	roamingDefault			(4),	-- For SGSN, S-GW and P-GW
	visitingDefault			(5)	-- For SGSN, S-GW and P-GW
}

DataVolumeMBMS	::= INTEGER (-9223372036854775808..9223372036854775807)
	--
	-- The volume of data transferred in octets.
	--

DataVolumeGPRS	::= INTEGER (-9223372036854775808..9223372036854775807)
	--
	-- The volume of data transferred in octets.
	--

DeferredLocationEventType ::= BIT STRING 
{
	msAvailable			(0) 
} (SIZE (1..16)) 

	-- exception handling
	-- a ProvideSubscriberLocation-Arg containing other values than listed above in 
	-- DeferredLocationEventType shall be rejected by the receiver with a return error cause of 
	-- unexpected data value.

DynamicAddressFlag	::= BOOLEAN

EPCQoSInformation	::= SEQUENCE
{
	--
	-- See TS 29.212 [88] for more information
	-- 
	qCI	                [1] INTEGER,
	maxRequestedBandwithUL	[2] INTEGER OPTIONAL,
	maxRequestedBandwithDL	[3] INTEGER OPTIONAL,
	guaranteedBitrateUL	[4] INTEGER OPTIONAL,
	guaranteedBitrateDL	[5] INTEGER OPTIONAL,
	aRP			[6] INTEGER OPTIONAL,
        aPNAggregateMaxBitrateUL  [7] INTEGER OPTIONAL,
        aPNAggregateMaxBitrateDL  [8] INTEGER OPTIONAL,
        extendedMaxRequestedBWUL  [9] INTEGER OPTIONAL,
        extendedMaxRequestedBWDL  [10] INTEGER OPTIONAL,
        extendedGBRUL             [11] INTEGER OPTIONAL,
        extendedGBRDL             [12] INTEGER OPTIONAL,
        extendedAPNAMBRUL         [13] INTEGER OPTIONAL,
        extendedAPNAMBRDL         [14] INTEGER OPTIONAL


}

ETSIAddress	::= AddressString
	--
	-- First octet for nature of address, and numbering plan indicator (3 for X.121)
	-- Other octets TBCD
	-- See TS 29.002 [60]
	--

Ext-GeographicalInformation ::= OCTET STRING (SIZE (1..maxExt-GeographicalInformation))
	-- Refers to geographical Information defined in 3G TS 23.032.
	-- This is composed of 1 or more octets with an internal structure according to
	-- 3G TS 23.032
	-- Octet 1: Type of shape, only the following shapes in 3G TS 23.032 are allowed:
	--		(a) Ellipsoid point with uncertainty circle
	--		(b) Ellipsoid point with uncertainty ellipse
	--		(c) Ellipsoid point with altitude and uncertainty ellipsoid
	--		(d) Ellipsoid Arc
	--		(e) Ellipsoid Point
	-- Any other value in octet 1 shall be treated as invalid
	-- Octets 2 to 8 for case (a) ¨C Ellipsoid point with uncertainty circle
	--		Degrees of Latitude				3 octets
	--		Degrees of Longitude				3 octets
	--		Uncertainty code				1 octet
	-- Octets 2 to 11 for case (b) ¨C Ellipsoid point with uncertainty ellipse:
	--		Degrees of Latitude				3 octets
	--		Degrees of Longitude				3 octets
	--		Uncertainty semi-major axis			1 octet
	--		Uncertainty semi-minor axis			1 octet
	--		Angle of major axis				1 octet
	--		Confidence					1 octet
	-- Octets 2 to 14 for case (c) ¨C Ellipsoid point with altitude and uncertainty ellipsoid
	--		Degrees of Latitude				3 octets
	--		Degrees of Longitude				3 octets
	--		Altitude					2 octets
	--		Uncertainty semi-major axis			1 octet
	--		Uncertainty semi-minor axis			1 octet
	--		Angle of major axis				1 octet
	--		Uncertainty altitude				1 octet
	--		Confidence					1 octet
	-- Octets 2 to 13 for case (d) ¨C Ellipsoid Arc
	--		Degrees of Latitude				3 octets
	--		Degrees of Longitude				3 octets
	--		Inner radius					2 octets
	--		Uncertainty radius				1 octet
	--		Offset angle					1 octet
	--		Included angle					1 octet
	--		Confidence					1 octet
	-- Octets 2 to 7 for case (e) ¨C Ellipsoid Point
	--		Degrees of Latitude				3 octets
	--		Degrees of Longitude				3 octets

	--
	-- An Ext-GeographicalInformation parameter comprising more than one octet and
	-- containing any other shape or an incorrect number of octets or coding according
	-- to 3G TS 23.032 shall be treated as invalid data by a receiver.
	--
	-- An Ext-GeographicalInformation parameter comprising one octet shall be discarded
	-- by the receiver if an Add-GeographicalInformation parameter is received 
	-- in the same message.
	--
	-- An Ext-GeographicalInformation parameter comprising one octet shall be treated as
	-- invalid data by the receiver if an Add-GeographicalInformation parameter is not
	-- received in the same message.

FFDAppendIndicator	::= BOOLEAN

Flows  ::= 	SEQUENCE
	--
	-- See Flows AVP as defined in TS 29.214 [89] 
	--
{
	mediaComponentNumber	[1] INTEGER,
	flowNumber  		[2] SEQUENCE OF INTEGER OPTIONAL
}

FreeFormatData	::=	OCTET STRING (SIZE(1..160))
	--
	-- Free formated data as sent in the FurnishChargingInformationGPRS 
	-- see TS 29.078 [66]
	--

GSNAddress	::= IPAddress


IMEI ::= TBCD-STRING (SIZE (8))
	--	Refers to International Mobile Station Equipment Identity
	--	and Software Version Number (SVN) defined in TS GSM 03.03.
	--	If the SVN is not present the last octet shall contain the
	--	digit 0 and a filler.
	--	If present the SVN shall be included in the last octet.


IMSI ::= TBCD-STRING (SIZE (3..8))
	-- digits of MCC, MNC, MSIN are concatenated in this order.

SGWChange	::= BOOLEAN
	--
	-- present if first record after inter S-GW change
	--

IPAddress	::= CHOICE
{
	iPBinaryAddress	 IPBinaryAddress,
	iPTextRepresentedAddress	 IPTextRepresentedAddress
}

IPBinaryAddress	::= CHOICE
{
	iPBinV4Address			[0] OCTET STRING (SIZE(4)),
	iPBinV6Address			[1] OCTET STRING (SIZE(16))
}

IPTextRepresentedAddress	::= CHOICE
{	
	--
	-- IP address in the familiar "dot" notation
	--
	iPTextV4Address			[2] IA5String (SIZE(7..15)),
	iPTextV6Address			[3] IA5String (SIZE(15..45))
}

ISDN-AddressString ::= 
			AddressString (SIZE (1..maxISDN-AddressLength))
	-- This type is used to represent ISDN numbers.

LCSCause				::= OCTET STRING (SIZE(1))
	--
	-- See LCS Cause Value, TS 49.031 [71]
	--

LCSClientIdentity 		::= SEQUENCE 
{
	lcsClientExternalID	[0] LCSClientExternalID OPTIONAL,
	lcsClientDialedByMS	[1] AddressString OPTIONAL,
	lcsClientInternalID	[2] LCSClientInternalID OPTIONAL   
}

LCSQoSInfo				::= OCTET STRING (SIZE(4))
	--
	-- See LCS QoS IE, TS 49.031 [71]
	--

LCSClientExternalID ::= SEQUENCE 
{
	externalAddress		[0] AddressString	OPTIONAL
--	extensionContainer	[1] ExtensionContainer	OPTIONAL
}

LCSClientInternalID ::= ENUMERATED 
{
	broadcastService		(0),
	o-andM-HPLMN			(1),
	o-andM-VPLMN			(2),
	anonymousLocation		(3),
	targetMSsubscribedService	(4)
}
	-- for a CAMEL phase 3 PLMN operator client, the value targetMSsubscribedService shall be used


LCS-Priority ::= OCTET STRING (SIZE (1))
	-- 0 = highest priority
	-- 1 = normal priority
	-- all other values treated as 1 

LocalSequenceNumber ::= INTEGER (0..4294967295)
	--
	-- Sequence number of the record in this node
	-- 0.. 4294967295 is equivalent to 0..2**32-1, unsigned integer in four octets

LocationMethod ::= ENUMERATED 
{
	msBasedEOTD			(0),
	msAssistedEOTD			(1),
	assistedGPS			(2), 
	msBasedOTDOA			(3),
	msAssistedOTDOA			(4)
}
	-- exception handling:
	-- When this parameter is received with value msBasedEOTD or msAssistedEOTD and the MS 
	-- is camped on an UMTS Service Area then the receiver shall reject it 
	-- with a return error cause of unexpected data value.
	-- When this parameter is received with value msBasedOTDOA or msAssistedOTDOA and the MS 
	-- is camped on a GSM Cell then the receiver shall reject it with a return error cause of
	-- unexpected data value.
	-- an unrecognized value shall be rejected by the receiver with a return error cause of
	-- unexpected data value.

LocationAreaAndCell		::= SEQUENCE
{
	locationAreaCode		[0] LocationAreaCode,
	cellId				[1] CellId,	
	mCC-MNC		                [2] MCC-MNC 	OPTIONAL
}

MSISDN	::= ISDN-AddressString 
	-- 
	-- See TS 23.003 [68]
	--

ManagementExtension ::= SEQUENCE 
{
	identifier	OBJECT IDENTIFIER,
	significance	[1] BOOLEAN DEFAULT FALSE,
	information	[2] OCTET STRING 
}

MSNetworkCapability	::= OCTET STRING (SIZE(1..8))
	-- see TS 24.008 [64]

NetworkInitiatedPDPContext	::= BOOLEAN
	--
	-- Set to true if PDP context was initiated from network side
	--

NodeID	::= IA5String (SIZE(1..20))

NumberOfDPEncountered  ::= INTEGER

maxAddressLength  INTEGER ::= 20

maxISDN-AddressLength  INTEGER ::= 9

maxExt-GeographicalInformation  INTEGER ::= 20
	-- the maximum length allows for further shapes in 3G TS 23.032 to be included in later 
	-- versions of 3G TS 29.002

NotificationToMSUser ::= ENUMERATED 
{
	notifyLocationAllowed				(0),
	notifyAndVerify-LocationAllowedIfNoResponse	(1),
	notifyAndVerify-LocationNotAllowedIfNoResponse	(2),
	locationNotAllowed 				(3) 
}
	-- exception handling:
	-- At reception of any other value than the ones listed the receiver shall ignore
	-- NotificationToMSUser.

LCSClientType ::= ENUMERATED 
{
	emergencyServices		(0),
	valueAddedServices		(1),
	plmnOperatorServices		(2),
	lawfulInterceptServices		(3)
}
	--	exception handling:
	--	unrecognized values may be ignored if the LCS client uses the privacy override
	--	otherwise, an unrecognized value shall be treated as unexpected data by a receiver
	--	a return error shall then be returned if received in a MAP invoke 

LocationType ::= SEQUENCE 
{
	locationEstimateType		[0] LocationEstimateType,
	deferredLocationEventType	[1] DeferredLocationEventType	OPTIONAL 
}

LocationEstimateType ::= ENUMERATED 
{
	currentLocation			(0),
	currentOrLastKnownLocation	(1),
	initialLocation			(2),
	activateDeferredLocation	(3),
	cancelDeferredLocation		(4) 
}
	--	exception handling:
	--	a ProvideSubscriberLocation-Arg containing an unrecognized LocationEstimateType
	--	shall be rejected by the receiver with a return error cause of unexpected data value	
	
PDPAddress	::= CHOICE
{
	iPAddress				[0] IPAddress,
	eTSIAddress				[1] ETSIAddress
}

PDPType		::= OCTET STRING (SIZE(2))
	--
	-- OCTET 1: PDP Type Organization
	-- OCTET 2: PDP Type Number
	-- See TS 29.060 [75]
	--


QoSInformation	::= OCTET STRING (SIZE (4..255))
	--
	-- This  octet string 
	-- is a 1:1 copy of the contents (i.e. starting with octet 4) of the "Quality of 
	-- service Profile" information element specified in TS 29.060 [75].
	--	

RoutingAreaCode	::= OCTET STRING (SIZE(1))
	--
	-- See TS 24.008 [64]	
	--

--ExtensionContainer ::= SEQUENCE 
--{
--	privateExtensionList	[0] PrivateExtensionList	OPTIONAL, 
--	pcs-Extensions		[1] PCS-Extensions		OPTIONAL
--}

--PrivateExtensionList ::= SEQUENCE SIZE (1..maxNumOfPrivateExtensions) OF PrivateExtension

--PrivateExtension ::= SEQUENCE 
--{
--	extId		MAP-EXTENSION.&extensionId	({ExtensionSet}),
--	extType		MAP-EXTENSION.&ExtensionType	({ExtensionSet}{@extId})	OPTIONAL
--}

--maxNumOfPrivateExtensions  INTEGER ::= 10

--ExtensionSet		MAP-EXTENSION ::=
--{
	 -- ExtensionSet is the set of all defined private extensions
--}
	-- Unsupported private extensions shall be discarded if received.

--PCS-Extensions ::= SEQUENCE 
--{
--}

--MAP-EXTENSION  ::= CLASS 
--{
--	&ExtensionType		OPTIONAL,
--	&extensionId 		OBJECT IDENTIFIER 
--}
	-- The length of the Object Identifier shall not exceed 16 octets and the
	-- number of components of the Object Identifier shall not exceed 16

SCFAddress	::= AddressString
	--
	-- See TS 29.002 [60]
	--

ServiceKey ::= INTEGER (0..2147483647)

SGSNChange	::= BOOLEAN
	--
	-- present if first record after inter SGSN routing area update
	-- in new SGSN
	--


SMSResult					::= Diagnostics

TBCD-STRING ::= OCTET STRING
	-- This type (Telephony Binary Coded Decimal String) is used to
	-- represent several digits from 0 through 9, *, #, a, b, c, two
	-- digits per octet, each digit encoded 0000 to 1001 (0 to 9),
	-- 1010 (*), 1011 (#), 1100 (a), 1101 (b) or 1110 (c); 1111 used
	-- as filler when there is an odd number of digits.

	-- bits 8765 of octet n encoding digit 2n
	-- bits 4321 of octet n encoding digit 2(n-1) +1

PositionMethodFailure-Diagnostic ::= ENUMERATED {
	congestion  (0),
	insufficientResources  (1),
	insufficientMeasurementData  (2),
	inconsistentMeasurementData  (3),
	locationProcedureNotCompleted  (4),
	locationProcedureNotSupportedByTargetMS  (5),
	qoSNotAttainable  (6),
	positionMethodNotAvailableInNetwork	(7),
	positionMethodNotAvailableInLocationArea	(8)
}
--	exception handling:
--	any unrecognized value shall be ignored

UnauthorizedLCSClient-Diagnostic ::= ENUMERATED {
	noAdditionalInformation (0),
	clientNotInMSPrivacyExceptionList (1),
	callToClientNotSetup (2),
	privacyOverrideNotApplicable (3),
	disallowedByLocalRegulatoryRequirements (4)
}
--	exception handling:
--	any unrecognized value shall be ignored

PLMN-Id		::= OCTET STRING (SIZE (3))
	--
	--	This is a 1:1 copy from the Routing Area Identity (RAI) IE specified in TS 29.060 [75]
	--  as follows:
	--	OCTET 1 of PLMN-Id = OCTET 2 of RAI  
	--	OCTET 2 of PLMN-Id = OCTET 3 of RAI  
	--	OCTET 3 of PLMN-Id = OCTET 4 of RAI  
	--

PositioningData	::= OCTET STRING (SIZE(1..33))
	--
	-- See Positioning Data IE (octet 3..n), TS 49.031 [71]
	--
RATType	::= INTEGER (0..255)
	--
	-- Ihis integer is 1:1 copy of the RAT type value as defined in TS 29.060 [75].
	--

PSFurnishChargingInformation  ::= SEQUENCE
{
	pSFreeFormatData	[1] FreeFormatData,
	pSFFDAppendIndicator  	[2] FFDAppendIndicator OPTIONAL
}

MSTimeZone	::= OCTET STRING (SIZE (2))
	--
	-- 1.Octet: Time Zone and 2. Octet: Daylight saving time, see TS 29.060 [75]
	--

ChangeOfServiceCondition	::= SEQUENCE
{
	--
	-- Used for Flow based Charging service data container
	--
	ratingGroup 			[1] RatingGroupId OPTIONAL,
	chargingRuleBaseName		[2] ChargingRuleBaseName OPTIONAL,
	resultCode			[3] ResultCode OPTIONAL,
	localSequenceNumber		[4] LocalSequenceNumber OPTIONAL,
	timeOfFirstUsage		[5] TimeStamp OPTIONAL,
	timeOfLastUsage			[6] TimeStamp OPTIONAL,
	timeUsage 			[7] CallDuration OPTIONAL,
	serviceConditionChange		[8] ServiceConditionChange,
	qoSInformationNeg		[9] QoSInformation OPTIONAL,
	sgsnAddress 			[10] GSNAddress OPTIONAL,
	sGSNPLMNIdentifier 		[11] PLMN-Id OPTIONAL,
	datavolumeFBCUplink		[12] DataVolumeGPRS OPTIONAL,
	datavolumeFBCDownlink		[13] DataVolumeGPRS OPTIONAL,
	timeOfReport			[14] TimeStamp,
	rATType				[15] RATType OPTIONAL,
	failureHandlingContinue		[16] FailureHandlingContinue OPTIONAL,
	serviceIdentifier		[17] ServiceIdentifier OPTIONAL,
	pSFurnishChargingInformation	[18] PSFurnishChargingInformation OPTIONAL,
	aFRecordInformation		[19] SEQUENCE OF AFRecordInformation OPTIONAL,
	userLocationInformation		[20] OCTET STRING OPTIONAL,
	eventBasedChargingInformation	[21] EventBasedChargingInformation OPTIONAL,
	timeQuotaMechanism		[22] TimeQuotaMechanism OPTIONAL
}

ChangeOfServiceConditions	::= SEQUENCE
{
	--
	-- Used for Flow based Charging service data container
	--
	ratingGroup 			[1] RatingGroupId OPTIONAL,
	chargingRuleBaseName		[2] ChargingRuleBaseName OPTIONAL,
	resultCode			[3] ResultCode OPTIONAL,
	localSequenceNumber		[4] LocalSequenceNumber OPTIONAL,
	timeOfFirstUsage		[5] TimeStamp OPTIONAL,
	timeOfLastUsage			[6] TimeStamp OPTIONAL,
	timeUsage 			[7] CallDuration OPTIONAL,
	serviceConditionChange		[8] ServiceConditionChange,
	qoSInformationNeg		[9] EPCQoSInformation OPTIONAL,
	sgsnAddress 			[10] GSNAddress OPTIONAL,
	sGSNPLMNIdentifier 		[11] PLMN-Id OPTIONAL,
	datavolumeFBCUplink		[12] DataVolumeGPRS OPTIONAL,
	datavolumeFBCDownlink		[13] DataVolumeGPRS OPTIONAL,
	timeOfReport			[14] TimeStamp,
	rATType				[15] RATType OPTIONAL,
	failureHandlingContinue		[16] FailureHandlingContinue OPTIONAL,
	serviceIdentifier		[17] ServiceIdentifier OPTIONAL,
	pSFurnishChargingInformation	[18] PSFurnishChargingInformation OPTIONAL,
	aFRecordInformation		[19] SEQUENCE OF AFRecordInformation OPTIONAL,
	userLocationInformation		[20] OCTET STRING OPTIONAL,
	eventBasedChargingInformation	[21] EventBasedChargingInformation OPTIONAL,
	timeQuotaMechanism		[22] TimeQuotaMechanism OPTIONAL
}

RatingGroupId ::= INTEGER
	-- 
	-- IP service flow identity (DCCA), range of 4 byte (0...4294967259)
	-- see Rating-Group AVP as used in 3GPP TS 32.299 [40]
	--

ChargingRuleBaseName ::= IA5String (SIZE(1..16))
	-- 
	-- identifier for the group of charging rules
	-- see Charging-Rule-Base-Name AVP as desined in TS 29.212 [88]
	--

ResultCode ::= INTEGER
-- 
	-- charging protocol return value, range of 4 byte (0...4294967259)
	-- see Result-Code AVP as used in 3GPP 29.212 [88]
	--

ServiceConditionChange	::= BIT STRING 
{
	qoSChange 				(0),	-- PDP context modification
	sGSNChange 				(1), 	-- PDP context modification
	sGSNPLMNIDChange 			(2), 	-- PDP context modification
	tariffTimeSwitch 			(3), 	-- tariff time change
	pDPContextRelease 			(4), 	-- PDP context release
	rATChange 				(5),	-- PDP context modification
	serviceIdledOut 			(6),	-- IP flow idle out, DCCA QHT expiry
	reserved1 				(7),	-- old: QCTexpiry is no report event
	configurationChange 			(8),	-- configuration change
	serviceStop 				(9), 	-- IP flow termination
	dCCATimeThresholdReached 		(10),	-- DCCA quota reauthorization
	dCCAVolumeThresholdReached 		(11), 	-- DCCA quota reauthorization
	dCCAServiceSpecificUnitThresholdReached	(12), 	-- DCCA quota reauthorization
	dCCATimeExhausted 			(13), 	-- DCCA quota reauthorization
	dCCAVolumeExhausted 			(14), 	-- DCCA quota reauthorization
	dCCAValidityTimeout 			(15), 	-- DCCA quota validity time (QVT expiry)
	reserved2				(16),	-- reserved due to no use case, 
													-- old: return Requested is covered by (17),(18)
	dCCAReauthorisationRequest 		(17), 	-- DCCA quota reauthorization request by OCS
	dCCAContinueOngoingSession 		(18), 	-- DCCA failure handling (CCFH),
													-- continue IP flow
	dCCARetryAndTerminateOngoingSession	(19), 	-- DCCA failure handling (CCFH),
													-- terminate IP flow after DCCA retry
	dCCATerminateOngoingSession 		(20), 	-- DCCA failure handling,
													-- terminate IP flow
	cGI-SAIChange				(21), 	-- PDP context modification
	rAIChange				(22), 	-- PDP context modification
	dCCAServiceSpecificUnitExhausted	(23), 	-- DCCA quota reauthorization
	recordClosure				(24),	-- eG-CDR closure
	timeLimit				(25),	-- intermediate recording
	volumeLimit				(26),	-- intermediate recording
	serviceSpecificUnitLimit		(27),	-- intermediate recording
	envelopeClosure 			(28),
        eCGIChange				(29), 	-- bearer modification. "ECGI Change"
	tAIChange				(30), 	-- bearer modification. "TAI Change"
	userLocationChange			(31)	-- bearer modification. "User Location Change"

} 
-- Trigger and cause values for IP flow level recording are defined for support of independent
-- online and offline charging and also for tight interworking between online and offline charging.
-- Unused bits will always be zero.
-- Some of the values are non-exclusive (e.g. PDP context modification reasons).


FailureHandlingContinue  ::= BOOLEAN
	--
-- This parameter is included when the failure handling procedure has been executed and new 
-- containers are opened. This parameter shall be included in the first and subsequent 
-- containers opened after the failure handling execution.
	--

ServiceIdentifier	::= INTEGER (0..4294967295)
	--
	-- The service identifier is used to identify the service or the service component
	-- the service data flow relates to. See Service-Identifier AVP as defined 
	-- in TS 29.212 [88]
	--


SmsTpDestinationNumber ::= OCTET STRING
	--
	-- This type contains the binary coded decimal representation of
	-- the SMS address field the encoding of the octet string is in 
	-- accordance with the definition of address fields in TS 23.040 [72].
	-- This encoding includes type of number and numbering plan indication
	-- together with the address value range.
	--

RAIdentity ::= OCTET STRING (SIZE (6))
-- Routing Area Identity is coded in accordance with 3GPP TS 29.060 [105].
-- It shall contain the value part defined in 3GPP TS 29.060 only. I.e. the 3GPP TS 29.060
-- type identifier octet shall not be included.


MBMSInformation			::= SET
{
	tmgi					 [1] TMGI,
	mbmsSessionIdentity			 [2] MBMSSessionIdentity OPTIONAL,
	mbmsServiceType				 [3] MBMSServiceType,
	mbmsUserServiceType			 [4] MBMSUserServiceType,
	mbms2G3GIndicator			 [5] MBMS2G3GIndicator OPTIONAL,
	fileRepairSupported			 [6] BOOLEAN OPTIONAL,
	rAI					 [7] RoutingAreaCode OPTIONAL,
	mbmsServiceArea				 [8] MBMSServiceArea OPTIONAL,
	requiredMBMSBearerCaps			 [9] RequiredMBMSBearerCapabilities OPTIONAL
}
MBMS2G3GIndicator		::= ENUMERATED
{
	for-2G			(0),	-- For GERAN access only
	for-3G			(1),	-- For UTRAN access only
	for-2G-AND-3G		(2)	-- For both UTRAN and GERAN access
}

MBMSServiceType		::= ENUMERATED
{
	multicast		(0),
	broadcast		(1)
}

MBMSUserServiceType		::= ENUMERATED
{
	download		(0),
	streaming		(1)
}

RequiredMBMSBearerCapabilities		::= OCTET STRING (SIZE (3..14))
	--
	-- This  octet string 
	-- is a 1:1 copy of the contents (i.e. starting with octet 5) of the "Quality of 
	-- service Profile" information element specified in 3GPP TS 29.060.

MBMSSessionIdentity		::= OCTET STRING (SIZE (1))
	--
	-- This octet string is a 1:1 copy of the contents of the MBMS-Session-Identity
	-- AVP specified in 3GPP TS 29.061
TMGI		::= OCTET STRING
	--
	-- This  octet string 
	-- is a 1:1 copy of the contents (i.e. starting with octet 4) of the "TMGI" 
	-- information element specified in 3GPP TS 29.060.
MBMSServiceArea		::= OCTET STRING
	--
	-- Editor's Note: The structure of this octet string is subject to discussions
	-- in other working groups.

ContentInfo  ::= SEQUENCE 
{
	extensionType			[0] INTEGER,
	length				[1] INTEGER,
	serviceList     		[2] SEQUENCE --<UNBOUNDED>-- OF ServiceEvent OPTIONAL,
	changeTimeList			[3] SEQUENCE OF ChangeTimeExtension OPTIONAL,
	recordOpeningTime		[4] TimeStampExtension OPTIONAL,
	duration	    		[5] CallDurationExtension OPTIONAL,
	transparentVSA    		[6] OCTET STRING (SIZE(3..255)) OPTIONAL,
	cdrType               		[7] BOOLEAN OPTIONAL,
	createTime			[8] TimeStamp  OPTIONAL,    
	chargingType			[9] INTEGER OPTIONAL,
	roaming      			[10] BOOLEAN OPTIONAL,
	profile				[11] ProfileID OPTIONAL,
	nsapi				[12] INTEGER OPTIONAL,
	lastActivityTimeUpLink		[13] TimeStamp OPTIONAL,
	lastActivityTimeDownLink	[14] TimeStamp OPTIONAL,
	zoneId				[15] INTEGER OPTIONAL,
	daylightSavingTime		[16] INTEGER OPTIONAL,
	localTimeZone			[17] INTEGER OPTIONAL,
	sgsnChange			[18] BOOLEAN OPTIONAL,   
	sessionID			[19] ChargingID OPTIONAL,
	recordOpeningTimeZone		[20] INTEGER OPTIONAL,
	saRecordChangeTime		[21] TimeStamp OPTIONAL,
	saRecordChangeTimeZone		[22] INTEGER OPTIONAL
}

ServiceEvent ::= SEQUENCE
{
    serviceCode   		[0]  INTEGER OPTIONAL,
    uplinkVolume		[1]  DataVolumeGPRS OPTIONAL,
    downlinkVolume		[2]  DataVolumeGPRS OPTIONAL,
    usageduration		[3]  INTEGER OPTIONAL,
    url				[5]  OCTET STRING (SIZE(1..120)) OPTIONAL, 
    chargingRuleBaseName	[8]  ChargingRuleBaseName OPTIONAL,
    ratingGroup 		[9] RatingGroupId OPTIONAL,
    serviceIdentifier		[10] ServiceIdentifier OPTIONAL,
    localSequenceNumber		[11] LocalSequenceNumber OPTIONAL,
    envelopeStartTime		[12] TimeStampExtension OPTIONAL,
    envelopeEndTime    		[13] TimeStampExtension OPTIONAL,
    duration			[14] CallDurationExtension OPTIONAL,
    changeTimeTimeZone      [15] INTEGER OPTIONAL,
    noOCSCreditControl     	[16] BOOLEAN OPTIONAL
}

ProfileID	::= INTEGER (0..4294967295)

TimeZone ::= INTEGER

CallDurationExtension			::= OCTET STRING (SIZE(3..12))
	-- The contents of this field are 2^32 - 1. Variable with one digit after the comma
	-- Value is in seconds with one digit after the comma

EventBasedChargingInformation  ::= SEQUENCE
{
	numberOfEvents		[1] INTEGER,
	eventTimeStamps  	[2] SEQUENCE OF TimeStamp OPTIONAL
}

TimeQuotaMechanism	::= SEQUENCE
{
	timeQuotaType					[1] TimeQuotaType,
	baseTimeInterval				[2] INTEGER
}

TimeQuotaType	::= ENUMERATED
{
	discreteTimePeriod			(0),
	continuousTimePeriod			(1),
	continousTimePeriodExtension	(100)
}

ChangeTimeExtension ::= SEQUENCE
{
	changeTime  [1]  TimeStampExtension OPTIONAL,
	changeTimeTimeZone	[2] 	INTEGER OPTIONAL
}


TimeStampExtension			::= OCTET STRING (SIZE(10))
	--
	-- The contents of this field are a compact form of the UTCTime format
	-- containing local time plus an offset to universal time. Binary coded
	-- decimal encoding is employed for the digits to reduce the storage and
	-- transmission overhead
	-- e.g. yymmddhhmmsss Suuvv	
	-- where
	-- YY 	= 	Year 00 to 99		BCD encoded
	-- MM 	= 	Month 01 to 12 	BCD encoded
	-- DD	=	Day 01 to 31		BCD encoded
	-- hh	=	hour 00 to 23		BCD encoded
	-- mm	=	minute 00 to 59	BCD encoded
	-- ss	=	second 00 to 59	BCD encoded
	-- s	= 	1/ 10 of a second: 0 to 9 BCD encoded
	-- S	=	Sign 0 = "+", "-"	ASCII encoded
	-- hh	=	hour 00 to 23		BCD encoded
	-- mm	=	minute 00 to 59	BCD encoded

ServingNodeType                ::= ENUMERATED
{
        --
        -- See  S5-091084.doc
        --
        sGSN                            (0),
        pMIPSGW                         (1),
        gTPSGW                          (2),
        ePDG                            (3),
        hSGW                            (4),
        mME                             (5)
}

SubscriptionID	::= SET
{
	subscriptionIDType	[0]	SubscriptionIDType,
	subscriptionIDData	[1]	UTF8String
}

SubscriptionIDType	::= ENUMERATED
{
	endUserE164		(0),
	endUserIMSI		(1),
	endUserSIPURI    	(2),
	endUserNAI		(3),
	endUserPrivate   	(4)
}

CSGAccessMode ::= ENUMERATED 
{
	closedMode		(0),
	hybridMode		(1)
}

CSGId	::= OCTET STRING (SIZE(4))
	--
	-- Defined in 23.003[xx]. Coded according to TS 29.060[xx] for GTP, and in TS 29.274 [xx] for eGTP  
	-- 24.008 [xx]	
	--

UserCSGInformation	::= SEQUENCE
{
	cSGId					[0] CSGId,
	cSGAccessMode				[1] CSGAccessMode,
	cSGMembershipIndication 		[2] NULL OPTIONAL
}

RANSecondaryRATUsageReport   ::= SEQUENCE
{
    dataVolumeUplink             [1] DataVolumeGPRS,
    dataVolumeDownlink           [2] DataVolumeGPRS,
    rANStartTime                 [3] TimeStamp,
    rANEndTime                   [4] TimeStamp,
    secondaryRATType             [5] SecondaryRATType OPTIONAL
}

SecondaryRATType  ::= INTEGER
{   
    reserved       (0),
    nR             (1)    -- New Radio 5G
}



END
